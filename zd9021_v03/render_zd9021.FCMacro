import os,traceback
import FreeCAD as App
import FreeCADGui as Gui
from PySide import QtCore
def settle():
    Gui.updateGui()
    loop=QtCore.QEventLoop()
    QtCore.QTimer.singleShot(700,loop.quit)
    loop.exec_()
OUT='/Users/byeongjangkim/MyProjects/Robots/cad/zd9021_v03'
try:
    d=App.openDocument(OUT+'/ZD9021V3_assembly.FCStd')
    d.Label='ZD 9021-V3 v03 - 검측 플랫폼'
    for o in d.Objects:
        if o.TypeId=='Part::Feature':
            o.ViewObject.ShapeColor=tuple(o.DisplayColor[:3]);o.ViewObject.LineColor=(0.08,0.09,0.10)
            o.ViewObject.DisplayMode='Flat Lines';o.ViewObject.LineWidth=1.0
            o.ViewObject.Deviation=0.15;o.Visibility=True
        elif o.TypeId=='App::Link':o.Visibility=True
        elif o.TypeId=='App::Part':o.Visibility=True
    d.ComponentLibrary.Visibility=False;d.Exploded.Visibility=False;d.RobotDeck.Visibility=False
    view=Gui.activeDocument().activeView();view.viewAxonometric();view.fitAll();Gui.updateGui()
    settle();view.saveImage(OUT+'/rolling_chassis.png',1800,1300,'White')
    view.viewTop();view.fitAll();settle();view.saveImage(OUT+'/top.png',1800,1400,'White')
    view.viewRear();view.fitAll();settle();view.saveImage(OUT+'/side.png',1800,900,'White')
    d.RollingChassis.Visibility=False;d.Exploded.Visibility=True
    view.viewAxonometric();view.fitAll();settle();view.saveImage(OUT+'/exploded.png',1800,1500,'White')
    d.Exploded.Visibility=False;d.RollingChassis.Visibility=True;d.RobotDeck.Visibility=True
    view.viewAxonometric();view.fitAll();settle();view.saveImage(OUT+'/platform.png',1800,1400,'White')
    d.recompute();d.save()
    # Save a second ready-to-open file with chassis exposed, preserving assembly file default.
    d.RobotDeck.Visibility=False;view.fitAll();d.saveAs(OUT+'/ZD9021V3_chassis_view.FCStd')
    d.RobotDeck.Visibility=True;view.fitAll()
    d.saveAs(OUT+'/ZD9021V3_assembly.FCStd')
    App.closeDocument(d.Name)
    Gui.getMainWindow().close()
    open(OUT+'/render_complete.txt','w').write('Rendered chassis/top/side/exploded/platform and saved FreeCAD view state.\n')
except Exception:
    open(OUT+'/render_error.txt','w').write(traceback.format_exc())
    raise
