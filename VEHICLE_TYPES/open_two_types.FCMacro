import FreeCAD as A, FreeCADGui as G
from pathlib import Path
root=Path('/Users/byeongjangkim/MyProjects/Robots/cad/VEHICLE_TYPES')
for rel in ['01_ZD9021V3/TypeA_ZD9021V3.FCStd','02_DIY_10KG_PAYLOAD/TypeB_DIY_10kg_R2.FCStd']:
 path=str(root/rel)
 doc=next((d for d in A.listDocuments().values() if d.FileName==path),None)
 if doc is None:doc=A.openDocument(path)
 A.setActiveDocument(doc.Name)
 G.activeDocument().activeView().viewAxonometric()
 G.activeDocument().activeView().fitAll()
# Read/open only: never save or overwrite either source.
