import FreeCAD as A, FreeCADGui as G
from pathlib import Path
from PySide6 import QtCore
p=Path('/Users/byeongjangkim/MyProjects/Robots/cad/VEHICLE_TYPES/03_INDEPENDENT_4WD')
d=A.openDocument(str(p/'TypeC_Independent4WD_R0.FCStd'))
v=G.activeDocument().activeView();v.viewAxonometric();v.fitAll()
loop=QtCore.QEventLoop();QtCore.QTimer.singleShot(1800,loop.quit);loop.exec()
for key in ['Assembly','Chassis']:
 d.getObject('Deck').Visibility=(key=='Assembly');d.getObject('Equipment').Visibility=(key=='Assembly')
 v.fitAll();v.getCameraOrientation();node=v.getCameraOrientation()
 c=v.getCameraNode();c.nearDistance.setValue(0.1);c.farDistance.setValue(100000)
 G.updateGui();v.saveImage(str(p/(key+'.png')),1800,1300,'White')
d.getObject('Deck').Visibility=True;d.getObject('Equipment').Visibility=True;v.fitAll();d.save()
