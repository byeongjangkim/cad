import FreeCAD as A, FreeCADGui as G, Part, math, json, pathlib, traceback
from FreeCAD import Vector as V
from PySide6 import QtCore
OUT=pathlib.Path('/Users/byeongjangkim/MyProjects/Robots/cad/VEHICLE_TYPES/02_DIY_10KG_PAYLOAD')
try:
 d=A.newDocument('TypeB_DIY_10kg_R1');d.Label='B형 · 적재10kg · 4모터 전륜조향 · 배치검토 R1'
 groups={}
 for key,label in [('Frame','01 가공 샤시 · 잠정 치수'),('Motors','02 모터·감속기 · 미선정 예약'),('Suspension','03 구매 현가 후보 · 치수 미확인 공간모델'),('Drive','04 CV 및 연결부 · 인터페이스 미확정'),('Steering','05 전륜 조향 · 기구 배치 검토'),('Wheels','06 ARA550059 · Ø169×81.5 규격 외형'),('Deck','07 가공 데크 및 지지대'),('Equipment','08 장비 및 배터리 · 공간 예약')]:
  o=d.addObject('App::Part',key);o.Label=label;groups[key]=o
 objects=[]
 silver=(.68,.72,.76);blue=(.16,.4,.62);orange=(.93,.49,.13);black=(.13,.14,.16);purple=(.62,.36,.68)
 def box(x,y,z,l,w,h):return Part.makeBox(l,w,h,V(x,y,z))
 def rod(a,b,r):
  a=V(*a);delta=V(*b)-a;return Part.makeCylinder(r,delta.Length,a,delta.normalize())
 def ring(ro,ri,l,pos,axis):return Part.makeCylinder(ro,l,V(*pos),V(*axis)).cut(Part.makeCylinder(ri,l,V(*pos),V(*axis)))
 def add(name,label,shape,group,color=silver,status='CUSTOM_PRELIMINARY',part='',source=''):
  if shape.isNull() or not shape.isValid():raise ValueError(name+' invalid shape')
  o=d.addObject('Part::Feature',name);o.Label=label;o.Shape=shape;groups[group].addObject(o)
  for prop,val in [('DesignStatus',status),('CandidatePartNumber',part),('SourceURL',source)]:
   o.addProperty('App::PropertyString',prop,'Traceability');setattr(o,prop,val)
  o.ViewObject.ShapeColor=color;objects.append(o);return o
 # Reference track 379.5 is inferred from 461 overall - 81.5 tire width. All hardpoints assumed.
 def purchase(name,label,shape,group,pn,pid):
  return add(name,label,shape,group,orange,'CATALOG_DIMENSIONS_ONLY; HARDPOINTS_UNVERIFIED',pn,'https://buyrc.co.kr/product/product_detail.asp?product_number='+str(pid))
 for y in (-60,60):
  add('Rail'+str(y).replace('-','N'),'가공 레일 480×20×25 t2 · 외측폭140 잠정',box(-240,y-10,70,480,20,25).cut(box(-241,y-8,72,482,16,21)),'Frame',blue)
 for x in (-200,-105,105,200):add('Cross'+str(x).replace('-','N'),'가공 크로스멤버 · 폭180 잠정',box(x-10,-90,75,20,180,20),'Frame',blue)
 for x,tag in [(180,'F'),(-180,'R')]:
  for side in (-1,1):
   code=tag+('L' if side>0 else 'R');y=side*80
   plate=box(x-48,y-25,95,96,50,5)
   for dx in (-35,35):
    slot=box(x+dx-2.75,y-10,94,5.5,20,7).fuse(Part.makeCylinder(2.75,7,V(x+dx,y-10,94))).fuse(Part.makeCylinder(2.75,7,V(x+dx,y+10,94)))
    plate=plate.cut(slot)
   add(code+'ModulePlate',code+' 탈착 현가 연결판 · Y조정20mm · 볼트체결 검토중',plate,'Frame',blue)
   for lev,z,length,pn,pid in [('Lower',105,67.5,'AR330381',99045),('Upper',145,46,'AR330380',99044)]:
    if tag=='R' and lev=='Upper':continue
    purchase(code+lev+'Pin',code+' 힌지핀 Ø4×'+str(length),rod((x-length/2,y,z),(x+length/2,y,z),2),'Suspension',pn,pid)
    for dx in (-length/2+5,length/2-5):
     b=box(x+dx-4,y-8,100,8,16,z-92).cut(rod((x+dx-5,y,z),(x+dx+5,y,z),2.1))
     add(code+lev+'Lug'+str(dx).replace('-','N').replace('.','_'),code+' 핀 지지 러그 · 축공/간격 잠정',b,'Frame',blue)
    outer=(x,side*165,84.5+(25 if lev=='Upper' else -20))
    shape=Part.makeCompound([rod((x-25,y,z),outer,5),rod((x+25,y,z),outer,5)])
    arm='AR330218' if lev=='Upper' else ('AR330219' if tag=='F' else 'AR330249')
    purchase(code+lev+'Arm',code+' '+arm+' 현가암 · 실물형상 미확인',shape,'Suspension',arm,99085 if lev=='Upper' else (99084 if tag=='F' else 99086))
   if tag=='R':purchase(code+'Camber',code+' AR330221 M5×89 캠버링크 · 조립길이 미확정',rod((x,side*80,145),(x,side*165,110),2.5),'Suspension','AR330221',99107)
   purchase(code+'Carrier',code+' '+('AR330505 조향블록' if tag=='F' else 'AR330404 후륜허브')+' · 공간모델',box(x-12,side*165-8,64.5,24,16,45),'Suspension','AR330505' if tag=='F' else 'AR330404',99103 if tag=='F' else 99047)
   if tag=='F':
    for z in (64.5,109.5):add(code+'PivotBall'+str(z).replace('.','_'),'전륜 피벗볼 · 규격 미확인',Part.makeSphere(6,V(x,side*165,z)),'Suspension',orange,'UNVERIFIED_ENVELOPE')
   length=115 if tag=='F' else 135
   a=V(x-18,side*140,87);b=a+V(-25,-side*35,(length**2-25**2-35**2)**0.5)
   purchase(code+'Shock',code+' GPM '+str(length)+'mm 쇼크 · 장착 중심거리 해석 잠정',Part.makeCompound([rod(tuple(a),tuple(b),2.5),rod(tuple(a+(b-a)*0.3),tuple(b),9)]),'Suspension','MAK115FAA-R-S' if tag=='F' else 'MAK135RAA-R-S',107520 if tag=='F' else 107221)
   add(code+'Tower',code+' 탈착 쇼크 타워 · 높이 잠정',box(b.x-7,b.y-6,100,14,12,b.z-93),'Frame',blue)
   # No selected motor/reducer mounting holes are released.
   mx=x+side*25
   add(code+'MotorReserve',code+' 모터+감속기 미선정 공간',box(mx-22,-65,112,44,130,44),'Motors',purple,'UNSELECTED_ENVELOPE')
   add(code+'OutputCup',code+' 출력 지지·구동컵 미선정',ring(8,4,16,(x,side*17,84.5),(0,side,0)),'Drive',purple,'INTERFACE_UNRESOLVED')
   purchase(code+'DriveShaft',code+' '+('AR310458 142mm' if tag=='F' else 'AR310459 139mm')+' · 중심좌표 미확정',rod((x,side*25,84.5),(x,side*165,84.5),3),'Drive','AR310458' if tag=='F' else 'AR310459',99029 if tag=='F' else 99041)
   purchase(code+'Axle',code+' Ø8 액슬 · 장착면 위치 미확인',rod((x,side*150,84.5),(x,side*(194.5 if tag=='F' else 195),84.5),4),'Drive','AR310590' if tag=='F' else 'AR310591',99028 if tag=='F' else 99110)
   purchase(code+'Tire',code+' ARA550059 Ø169×81.5 · 외형 단순화',ring(84.5,48.5,81.5,(x,side*149,84.5),(0,side,0)),'Wheels','ARA550059',103138).ViewObject.ShapeColor=black
   purchase(code+'Rim',code+' ARA550059 휠 · 17mm hex 위치 미확인',ring(48.5,8.5,25,(x,side*177.25,84.5),(0,side,0)),'Wheels','ARA550059',103138)
 purchase('Servo','RC935DMG 서보 · 외형/혼 미확인',box(55,-110,115,45,40,45),'Steering','RC935DMG',124575)
 add('ServoPlate','탈착 조향 받침판 · 홀 미확정',box(45,-115,105,100,160,5),'Frame',blue)
 purchase('Bellcrank','AR340073/AR340072 벨크랭크·연결판 공간모델',rod((130,-40,135),(130,40,135),5),'Steering','AR340073;AR340072',99098)
 for side in (-1,1):
  purchase('Tie'+str(side).replace('-','N'),'AR340071 M4×95 · 타이로드 조립길이 미확정',rod((130,side*40,135),(160,side*165,105),2),'Steering','AR340071',99106)
  add('SteerArm'+str(side).replace('-','N'),'전륜 조향암 · 범프스티어 미검증',rod((160,side*165,105),(180,side*165,105),5),'Steering',orange,'UNVERIFIED_ENVELOPE')
 add('ServoLink','서보→벨크랭크 · 혼 규격 미확인',rod((75,-85,150),(130,-40,135),3),'Steering',orange,'UNVERIFIED_ENVELOPE')
 for x in (-105,105):
  for y in (-60,60):add('DeckPost'+str(x).replace('-','N')+str(y).replace('-','N'),'데크 지지대',rod((x,y,95),(x,y,240),7),'Deck')
 add('DeckPlate','가공 상부 데크 320×260 t3 · 홀 보류',box(-160,-130,240,320,260,3),'Deck')
 add('Floor','배터리 받침 210×120 t3',box(-105,-60,95,210,120,3),'Frame')
 add('Battery','배터리 미선정',box(-95,-50,99,190,100,70),'Equipment',purple,'UNSELECTED_ENVELOPE')
 add('Lidar','LiDAR 미선정',Part.makeCylinder(35,55,V(-85,55,248)),'Equipment',purple,'UNSELECTED_ENVELOPE')
 add('Computer','제어보드 미선정',box(-50,-95,248,100,70,30),'Equipment',purple,'UNSELECTED_ENVELOPE')
 add('Camera','전방카메라 미선정',box(115,-25,248,40,50,35),'Equipment',purple,'UNSELECTED_ENVELOPE')
 notes=d.addObject('App::FeaturePython','DesignBasis');notes.Label='00 R1 · 부품후보 배치검토 · 가공 발주 불가'
 for key,value in [('Payload','10kg payload; gross mass TBD'),('Overall','529×461 mm straight nominal; track assumed'),('FrameWidth','140 mm rails; 180 mm crossmembers; preliminary'),('Hardpoints','UNVERIFIED: arm centers, bearing/hex offset, CV plunge, motor/reducer'),('ShockLength','115/135 catalog; eye centers and travel NOT confirmed'),('ShaftGeometry','display span140mm is NOT catalog joint-center length'),('Speed','0.1–2m/s; tire169 implies 11.3–226 wheel rpm'),('Mechanism','4 motors, front steering, rear camber links; motion not validated')]:
  notes.addProperty('App::PropertyString',key);setattr(notes,key,value)
 d.recompute();G.activateView('Gui::View3DInventor',True);v=G.activeDocument().mdiViewsOfType('Gui::View3DInventor')[0];v.setCameraOrientation(A.Rotation(V(0,0,1),45).multiply(A.Rotation(V(1,0,0),55)).Q);v.fitAll();G.updateGui()
 d.saveAs(str(OUT/'TypeB_DIY_10kg_R1.FCStd'))
 Part.export(objects,str(OUT/'TypeB_DIY_10kg_R1.step'))
 loop=QtCore.QEventLoop();QtCore.QTimer.singleShot(1200,loop.quit);loop.exec();v.setCameraOrientation(A.Rotation(V(0,0,1),45).multiply(A.Rotation(V(1,0,0),55)).Q);v.fitAll();G.updateGui();v.saveImage(str(OUT/'Assembly_R1.png'),1800,1300,'White')
 groups['Deck'].Visibility=False;groups['Equipment'].Visibility=False;v.fitAll();G.updateGui();v.saveImage(str(OUT/'Chassis_R1.png'),1800,1300,'White')
 groups['Deck'].Visibility=True;groups['Equipment'].Visibility=True;v.fitAll();d.save()
 result={'objects':len(objects),'invalid':[o.Name for o in objects if not o.Shape.isValid()],'motor_count':4,'payload_kg':10,'status':'PACKAGING_ONLY_NOT_MANUFACTURING_RELEASE','supplier_motor_step':False,'RC_suspension_geometry':'unverified envelopes','a_untouched':True}
 json.dump(result,open(OUT/'validation_R1.json','w'),indent=2);(OUT/'complete_R1.txt').write_text('done')
except Exception:
 (OUT/'error_R1.txt').write_text(traceback.format_exc());raise
