import FreeCAD as A, FreeCADGui as G, Part, math, json, pathlib, traceback
from FreeCAD import Vector as V
from PySide6 import QtCore
OUT=pathlib.Path('/Users/byeongjangkim/MyProjects/Robots/cad/VEHICLE_TYPES/02_DIY_10KG_PAYLOAD')
try:
 d=A.newDocument('TypeB_DIY_10kg_R3');d.Label='B형 · 적재10kg · 4모터 전륜조향 · 배치검토 R3'
 groups={}
 for key,label in [('Frame','01 가공 샤시 · 잠정 치수'),('Motors','02 모터·감속기 · 미선정 예약'),('Suspension','03 구매 현가 후보 · 치수 미확인 공간모델'),('Drive','04 CV 및 연결부 · 인터페이스 미확정'),('Steering','05 전륜 조향 · 기구 배치 검토'),('Wheels','06 ARA550059 · Ø169×81.5 규격 외형'),('Deck','07 가공 데크 및 지지대'),('Equipment','08 장비 및 배터리 · 공간 예약')]:
  o=d.addObject('App::Part',key);o.Label=label;groups[key]=o
 objects=[]
 silver=(.68,.72,.76);blue=(.16,.4,.62);orange=(.93,.49,.13);black=(.13,.14,.16);purple=(.62,.36,.68)
 def box(x,y,z,l,w,h):return Part.makeBox(l,w,h,V(x,y,z))
 def rod(a,b,r):
  a=V(*a);delta=V(*b)-a;return Part.makeCylinder(r,delta.Length,a,delta.normalize())
 def ring(ro,ri,l,pos,axis):return Part.makeCylinder(ro,l,V(*pos),V(*axis)).cut(Part.makeCylinder(ri,l,V(*pos),V(*axis)))
 def add(name,label,shape,group,color=silver,status='CUSTOM_PRELIMINARY',part='',source=''):
  if shape.isNull() or not shape.isValid():raise ValueError(name+' invalid shape')
  o=d.addObject('Part::Feature',name);o.Label=label;o.Shape=shape;groups[group].addObject(o)
  for prop,val in [('DesignStatus',status),('CandidatePartNumber',part),('SourceURL',source)]:
   o.addProperty('App::PropertyString',prop,'Traceability');setattr(o,prop,val)
  o.ViewObject.ShapeColor=color;objects.append(o);return o
 # Reference track 379.5 is inferred from 461 overall - 81.5 tire width. All hardpoints assumed.
 def purchase(name,label,shape,group,pn,pid):
  return add(name,label,shape,group,orange,'CATALOG_DIMENSIONS_ONLY; HARDPOINTS_UNVERIFIED',pn,'https://buyrc.co.kr/product/product_detail.asp?product_number='+str(pid))
 for y in (-60,60):
  add('Rail'+str(y).replace('-','N'),'가공 레일 480×20×25 t2 · 외측폭140 잠정',box(-240,y-10,70,480,20,25).cut(box(-241,y-8,72,482,16,21)),'Frame',blue)
 for x in (-200,-105,105,200):add('Cross'+str(x).replace('-','N'),'가공 크로스멤버 · 폭180 잠정',box(x-10,-90,75,20,180,20),'Frame',blue)
 for x,tag in [(180,'F'),(-180,'R')]:
  for side in (-1,1):
   code=tag+('L' if side>0 else 'R');y=side*80
   plate=box(x-48,y-25,95,96,50,5)
   for dx in (-35,35):
    slot=box(x+dx-2.75,y-10,94,5.5,20,7).fuse(Part.makeCylinder(2.75,7,V(x+dx,y-10,94))).fuse(Part.makeCylinder(2.75,7,V(x+dx,y+10,94)))
    plate=plate.cut(slot)
   add(code+'ModulePlate',code+' 탈착 현가 연결판 · Y조정20mm · 볼트체결 검토중',plate,'Frame',blue)
   for lev,z,length,pn,pid in [('Lower',105,67.5,'AR330381',99045),('Upper',145,46,'AR330380',99044)]:
    if tag=='R' and lev=='Upper':continue
    purchase(code+lev+'Pin',code+' 힌지핀 Ø4×'+str(length),rod((x-length/2,y,z),(x+length/2,y,z),2),'Suspension',pn,pid)
    for dx in (-length/2+5,length/2-5):
     b=box(x+dx-4,y-8,100,8,16,z-92).cut(rod((x+dx-5,y,z),(x+dx+5,y,z),2.1))
     add(code+lev+'Lug'+str(dx).replace('-','N').replace('.','_'),code+' 핀 지지 러그 · 축공/간격 잠정',b,'Frame',blue)
    outer=(x,side*165,84.5+(25 if lev=='Upper' else -20))
    shape=Part.makeCompound([rod((x-25,y,z),outer,5),rod((x+25,y,z),outer,5)])
    arm='AR330218' if lev=='Upper' else ('AR330219' if tag=='F' else 'AR330249')
    purchase(code+lev+'Arm',code+' '+arm+' 현가암 · 실물형상 미확인',shape,'Suspension',arm,99085 if lev=='Upper' else (99084 if tag=='F' else 99086))
   if tag=='R':purchase(code+'Camber',code+' AR330221 M5×89 캠버링크 · 조립길이 미확정',rod((x,side*80,145),(x,side*165,110),2.5),'Suspension','AR330221',99107)
   purchase(code+'Carrier',code+' '+('AR330505 조향블록' if tag=='F' else 'AR330404 후륜허브')+' · 공간모델',box(x-12,side*165-8,64.5,24,16,45),'Suspension','AR330505' if tag=='F' else 'AR330404',99103 if tag=='F' else 99047)
   if tag=='F':
    for z in (64.5,109.5):
     purchase(code+'PivotBall'+str(z).replace('.','_'),code+' AR330197 피벗볼 6×14×35 · 상세단차 미확인',Part.makeSphere(7,V(x,side*165,z)).fuse(rod((x,side*137,z),(x,side*165,z),3)),'Suspension','AR330197',99060)
   length=115 if tag=='F' else 135
   a=V(x-18,side*140,87);b=a+V(-25,-side*35,(length**2-25**2-35**2)**0.5)
   purchase(code+'Shock',code+' GPM '+str(length)+'mm 쇼크 · 장착 중심거리 해석 잠정',Part.makeCompound([rod(tuple(a),tuple(b),2.5),rod(tuple(a+(b-a)*0.3),tuple(b),9)]),'Suspension','MAK115FAA-R-S' if tag=='F' else 'MAK135RAA-R-S',107520 if tag=='F' else 107221)
   add(code+'Tower',code+' 탈착 쇼크 타워 · 높이 잠정',box(b.x-7,b.y-6,100,14,12,b.z-93),'Frame',blue)
   # Manufacturer envelope: 80 square, motor42 + gear41, output15 x35, axis13 above body centre.
   mx=x+side*45; zaxis=153; front=-side*7
   base_y=-90 if side>0 else 7
   motor_shape=box(mx-40,base_y,100,80,83,80).fuse(rod((mx,front,zaxis),(mx,side*28,zaxis),7.5))
   motor_shape=motor_shape.fuse(box(mx-2.5,min(side*1,side*26),zaxis+6,5,25,3))
   o=add(code+'MotorGear',code+' BLHM450K-GFS + GFS4G10 · 조건부 후보',motor_shape,'Motors',silver,'MANUFACTURER_DIMENSION_ENVELOPE; CONDITIONAL_NOT_PURCHASE_RELEASE','BLHM450K-GFS;GFS4G10','https://www.orientalmotor.com.sg/sg/products/detail?hinmei=BLHM450K-GFS%2BGFS4G10%2BBLH2D50-K%2BLHS003CC')
   plate=box(mx-46,min(front,front+side*6),94,92,6,92)
   plate=plate.cut(rod((mx,front-side,zaxis),(mx,front+side*7,zaxis),17.5))
   off=94/(2*math.sqrt(2))
   for dx in (-off,off):
    for dz in (-off,off):plate=plate.cut(rod((mx+dx,front-side,140+dz),(mx+dx,front+side*7,140+dz),3.25))
   add(code+'MotorPlate',code+' 모터 연결판 t6 · Ø94 PCD 4×Ø6.5 · 가공검토',plate,'Frame',blue)
   add(code+'MotorBase',code+' 모터 지지 크로스판 t5 · 체결 미확정',box(mx-46,-70,95,92,140,5),'Frame',blue)
   shaft_nominal=142 if tag=='F' else 139
   cup_y=165-math.sqrt(shaft_nominal**2-45**2-(153-84.5)**2)
   add(code+'AdapterReserve',code+' Ø15 키축→구동컵 어댑터 · 미선정',ring(12,7.5,cup_y-15,(mx,side*15,zaxis),(0,side,0)),'Drive',purple,'INTERFACE_UNRESOLVED; NO VERIFIED CUP BORE OR SUPPORT')
   add(code+'OutputCup',code+' 구동컵 공간 · 장착/지지 미확정',ring(10,5,12,(mx,side*(cup_y-6),zaxis),(0,side,0)),'Drive',purple,'UNVERIFIED_ENVELOPE')
   purchase(code+'DriveShaft',code+' '+('AR310458 142mm' if tag=='F' else 'AR310459 139mm')+' · 중심거리 가정',rod((mx,side*cup_y,zaxis),(x,side*165,84.5),3),'Drive','AR310458' if tag=='F' else 'AR310459',99029 if tag=='F' else 99041)
   purchase(code+'Axle',code+' Ø8 액슬 · 장착면 위치 미확인',rod((x,side*150,84.5),(x,side*(194.5 if tag=='F' else 195),84.5),4),'Drive','AR310590' if tag=='F' else 'AR310591',99028 if tag=='F' else 99110)
   purchase(code+'Tire',code+' ARA550059 Ø169×81.5 · 외형 단순화',ring(84.5,48.5,81.5,(x,side*149,84.5),(0,side,0)),'Wheels','ARA550059',103138).ViewObject.ShapeColor=black
   purchase(code+'Rim',code+' ARA550059 휠 · 17mm hex 위치 미확인',ring(48.5,8.5,25,(x,side*177.25,84.5),(0,side,0)),'Wheels','ARA550059',103138)
 purchase('Servo','RC935DMG 서보 · 외형/혼 미확인',box(55,-110,115,45,40,45),'Steering','RC935DMG',124575)
 add('ServoPlate','탈착 조향 받침판 · 홀 미확정',box(45,-115,105,100,160,5),'Frame',blue)
 purchase('Bellcrank','AR340073/AR340072 벨크랭크·연결판 공간모델',rod((130,-40,135),(130,40,135),5),'Steering','AR340073;AR340072',99098)
 for side in (-1,1):
  purchase('Tie'+str(side).replace('-','N'),'AR340071 M4×95 · 타이로드 조립길이 미확정',rod((130,side*40,135),(160,side*165,105),2),'Steering','AR340071',99106)
  add('SteerArm'+str(side).replace('-','N'),'전륜 조향암 · 범프스티어 미검증',rod((160,side*165,105),(180,side*165,105),5),'Steering',orange,'UNVERIFIED_ENVELOPE')
 add('ServoLink','서보→벨크랭크 · 혼 규격 미확인',rod((75,-85,150),(130,-40,135),3),'Steering',orange,'UNVERIFIED_ENVELOPE')
 for x in (-105,105):
  for y in (-60,60):add('DeckPost'+str(x).replace('-','N')+str(y).replace('-','N'),'데크 지지대',rod((x,y,95),(x,y,240),7),'Deck')
 add('DeckPlate','가공 상부 데크 320×260 t3 · 홀 보류',box(-160,-130,240,320,260,3),'Deck')
 add('Floor','배터리 받침 210×120 t3',box(-105,-60,95,210,120,3),'Frame')
 add('Battery','배터리 미선정',box(-95,-50,99,190,100,70),'Equipment',purple,'UNSELECTED_ENVELOPE')
 add('Lidar','LiDAR 미선정',Part.makeCylinder(35,55,V(-85,55,248)),'Equipment',purple,'UNSELECTED_ENVELOPE')
 add('Computer','제어보드 미선정',box(-50,-95,248,100,70,30),'Equipment',purple,'UNSELECTED_ENVELOPE')
 add('Camera','전방카메라 미선정',box(115,-25,248,40,50,35),'Equipment',purple,'UNSELECTED_ENVELOPE')
 # R3 interface details: bearing dimensions verified, axial coordinates provisional.
 for x,tag in [(180,'F'),(-180,'R')]:
  for side in (-1,1):
   code=tag+('L' if side>0 else 'R')
   carrier=d.getObject(code+'Carrier')
   carrier.Shape=carrier.Shape.cut(rod((x,side*150,84.5),(x,side*182,84.5),11))
   carrier.DesignStatus='CUTAWAY_ENVELOPE; NOT OEM bearing seats'
   carrier.Label += ' · 베어링 표시용 절개'
   purchase(code+'InnerBearing',code+' AR610018 내측 베어링 15×21×4',ring(10.5,7.5,4,(x,side*158,84.5),(0,side,0)),'Drive','AR610018',99015)
   purchase(code+'OuterBearing',code+' AR610016 외측 베어링 8×16×5',ring(8,4,5,(x,side*168,84.5),(0,side,0)),'Drive','AR610016',99013)
   axle=d.getObject(code+'Axle')
   axle.Shape=axle.Shape.fuse(rod((x,side*154,84.5),(x,side*163,84.5),7.5))
   axle.DesignStatus='NOMINAL8mm_SHAFT;15mm_BEARING_LAND_INFERRED; AXIAL_COORDINATES_UNVERIFIED'
   # 17 mm across-flat hex, catalog body length; not a wheel offset measurement.
   hlen=16.5 if tag=='F' else 13.6
   rr=17/math.sqrt(3);pts=[V(x+rr*math.cos(i*math.pi/3),side*174,84.5+rr*math.sin(i*math.pi/3)) for i in range(6)]
   wire=Part.makePolygon(pts+[pts[0]])
   h=Part.Face(wire).extrude(V(0,side*hlen,0)).cut(rod((x,side*173,84.5),(x,side*(175+hlen),84.5),4))
   purchase(code+'WheelHex',code+' '+('AR310484 17/16.5' if tag=='F' else 'AR310447 17/13.6')+' 헥스 · 오프셋 미확정',h,'Drive','AR310484' if tag=='F' else 'AR310447',99109 if tag=='F' else 99198)
   # Axial pin locations only show torque-transfer topology.
   purchase(code+'HexPin',code+' AR713009 헥스 구동핀 · 치수 미확인',rod((x-7,side*179,84.5),(x+7,side*179,84.5),1.25),'Drive','AR713009',0)
   d.getObject(code+'HexPin').SourceURL='https://www.horizonhobby.com/on/demandware.static/-/Sites-horizon-master/default/dw759b6c42/Manuals/ARA10604-Manual-MULTI.pdf'
   d.getObject(code+'HexPin').DesignStatus='SCHEMATIC_ONLY; NO VERIFIED PIN DIMENSIONS'
 # Frame connections: custom reinforcement; no strength certification implied.
 for x in (-105,105):
  for y in (-60,60):
   nm=str(x).replace('-','N')+str(y).replace('-','N')
   add('DeckFoot'+nm,'데크 기둥 하부 플랜지 · 체결 검토',box(x-15,y-15,98,30,30,5),'Deck',blue)
   for sign in (-1,1):
    pts=[V(x,y-3,105),V(x+sign*30,y-3,105),V(x,y-3,140)]
    gus=Part.Face(Part.makePolygon(pts+[pts[0]])).extrude(V(0,6,0))
    add('Gusset'+nm+str(sign).replace('-','N'),'데크 기둥 삼각 보강판 t6 · 잠정',gus,'Deck',blue)
 for x in (-180,180):
  for side in (-1,1):
   add('TowerBrace'+str(x).replace('-','N')+str(side).replace('-','N'),'쇼크 타워 대각 지지 · 잠정',rod((x-43,side*105,155),(x+25,side*80,100),5),'Frame',blue)
 # Independent drawing sheet records the drivetrain topology and unresolved interfaces.
 sheet=d.addObject('Spreadsheet::Sheet','InterfaceRegister');sheet.Label='09 연결 규격표 · 확인값/미확인값'
 rows=[['Part','Published dimension mm','Unverified'],['AR610018','15 x 21 x 4','Axial position, housing seat'],['AR610016','8 x 16 x 5','Axial position, housing seat'],['AR330197','6 x 14 x 35','Thread pitch, ball center offset'],['AR310484 front','17 hex / 16.5 nominal','Wheel offset'],['AR310447 rear','17 hex / 13.6 nominal','Wheel offset'],['AR310590 front','8 x 44.5','Stepped lengths, pin position'],['AR310591 rear','8 x 45','Stepped lengths, pin position'],['CV / dogbone','142 / 139 nominal','Center definition, plunge, torque'],['Motor -> gearbox -> cup','BLHM450K-GFS + GFS4G10 candidate','Cup/adapter and thermal validation pending'],['Bearing center gap','R3 display: 10.5','NOT MEASURED, NOT RELEASED']]
 for ri,row in enumerate(rows,1):
  for ci,val in enumerate(row):sheet.set(chr(65+ci)+str(ri),val)
 sheet.setColumnWidth('A',190);sheet.setColumnWidth('B',230);sheet.setColumnWidth('C',360)
 notes=d.addObject('App::FeaturePython','DesignBasis');notes.Label='00 R3 · 부품후보 배치검토 · 가공 발주 불가'
 for key,value in [('Payload','10kg payload; gross mass TBD'),('Overall','542×461 mm envelope including motor plates; track assumed'),('FrameWidth','140 mm rails; 180 mm crossmembers; preliminary'),('Hardpoints','UNVERIFIED: arm centers, bearing/hex offset, CV plunge, motor/reducer'),('ShockLength','115/135 catalog; eye centers and travel NOT confirmed'),('ShaftGeometry','142/139 treated as provisional center span; actual definition unknown'),('Speed','0.1–2m/s; tire169 implies 11.3–226 wheel rpm'),('Mechanism','4 motors, front steering, rear camber links; motion not validated')]:
  notes.addProperty('App::PropertyString',key);setattr(notes,key,value)
 d.recompute();G.activateView('Gui::View3DInventor',True);v=G.activeDocument().mdiViewsOfType('Gui::View3DInventor')[0];v.setCameraOrientation(A.Rotation(V(0,0,1),45).multiply(A.Rotation(V(1,0,0),55)).Q);v.fitAll();G.updateGui()
 d.saveAs(str(OUT/'TypeB_DIY_10kg_R3.FCStd'))
 Part.export(objects,str(OUT/'TypeB_DIY_10kg_R3.step'))
 loop=QtCore.QEventLoop();QtCore.QTimer.singleShot(1200,loop.quit);loop.exec();v.setCameraOrientation(A.Rotation(V(0,0,1),45).multiply(A.Rotation(V(1,0,0),55)).Q);v.fitAll();G.updateGui();v.saveImage(str(OUT/'Assembly_R3.png'),1800,1300,'White')
 groups['Deck'].Visibility=False;groups['Equipment'].Visibility=False;v.fitAll();G.updateGui();v.saveImage(str(OUT/'Chassis_R3.png'),1800,1300,'White')
 groups['Deck'].Visibility=True;groups['Equipment'].Visibility=True;v.fitAll();d.save()
 result={'objects':len(objects),'invalid':[o.Name for o in objects if not o.Shape.isValid()],'conditional_gearmotor_count':4,'released_motor_count':0,'payload_kg':10,'status':'PACKAGING_ONLY_NOT_MANUFACTURING_RELEASE','supplier_motor_step':False,'RC_suspension_geometry':'unverified envelopes','a_untouched':True}
 json.dump(result,open(OUT/'validation_R3.json','w'),indent=2);(OUT/'complete_R3.txt').write_text('done')
except Exception:
 (OUT/'error_R3.txt').write_text(traceback.format_exc());raise
