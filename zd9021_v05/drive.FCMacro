import FreeCAD as A, FreeCADGui as G, Part, math, json, traceback
from FreeCAD import Vector as V
from PySide import QtCore
OUT='/Users/byeongjangkim/MyProjects/Robots/cad/zd9021_v05'
try:
 d=A.openDocument('/Users/byeongjangkim/MyProjects/Robots/cad/zd9021_v04/ZD9021V3_equipped.FCStd')
 d.Label='ZD 9021-V3 v05 - 30kg 구동계 검토안'
 drive=d.addObject('App::Part','SelectedDrive');drive.Label='07 선정 구동계 (30kg 성능 미검증)'
 obsolete=d.addObject('App::Part','Superseded');obsolete.Label='08 교체 전 배치 (숨김)'
 replaced=['MotorMount8456','MotorAdapter8456','CenterSpur46T']
 for name in replaced:
  o=d.getObject(name)
  for parent in list(o.InList):
   if parent.TypeId=='App::Part':parent.removeObject(o)
  obsolete.addObject(o);o.Visibility=False
 new=[]
 def box(x,y,z,l,w,h):return Part.makeBox(l,w,h,V(x,y,z))
 def cyl(r,l,x,y,z):return Part.makeCylinder(r,l,V(x,y,z),V(1,0,0))
 def add(name,label,s,color,source,evidence):
  o=d.addObject('Part::Feature',name);o.Shape=s;o.Label=label;drive.addObject(o)
  for key,value in [('Source',source),('Evidence',evidence)]:o.addProperty('App::PropertyString',key,'Provenance');setattr(o,key,value)
  o.ViewObject.ShapeColor=color;o.ViewObject.LineColor=(.12,.12,.12)
  assert s.isValid() and s.Volume>0,name
  new.append(o);return o
 motorurl='https://www.hobbywing.com/products/xerunaxer3motor'
 escurl='https://www.hobbywing.com/en/index.php/products/xerunaxeplusr3'
 motor=cyl(21,74,-109,-29.5,95)
 # Manufacturer mounting pitch 25.4; M3 thread represented as pilot cavities, depth provisional.
 for zz in (95-12.7,95+12.7):motor=motor.cut(cyl(1.5,6,-41,-29.5,zz))
 add('AXE4274','HOBBYWING AXE4274 R3 1700KV / 30401401',motor,(.12,.13,.15),motorurl,'PUBLISHED body D42 x74; shaft D5; mounting pitch25.4. Hole depth/thread and detail simplified. 30kg continuous duty NOT verified.')
 add('MotorShaft','모터 출력축 D5 (돌출 길이 자료 차이 확인 필요)',cyl(2.5,20.5,-35,-29.5,95),(.7,.7,.72),motorurl,'D5 published. 20.5mm adopted from 20240627 manual; earlier manual gives18.5mm. Physical confirmation required.')
 gear=d.CenterSpur46T.Shape.copy();gear.translate(V(-37,0,0));gear=gear.cut(cyl(7.2,6,-23.5,0,95))
 support=d.getObject('CenterDiffSupportN22');placement=support.LinkPlacement.copy();placement.Base.x-=5;support.LinkPlacement=placement
 add('RelocatedSpur','ZD 8243 / 46T 스퍼 (반대쪽 배치 검토)',gear,(.6,.62,.64),'https://www.zd-racing.com/home/935-zd-racing-9021-v3-upgrade-parts-metal-46t-spur-gear-8243.html','46T published; mirrored axial layout requires differential assembly confirmation. Tooth form schematic; module1 assumed.')
 # Schematic 13T envelope, not machining geometry.
 teeth=[cyl(5.2,4,-22.5,-29.5,95)]
 for i in range(13):
  a=2*math.pi*i/13
  teeth.append(cyl(1.3,4,-22.5,-29.5+6.4*math.cos(a),95+6.4*math.sin(a)))
 pin=teeth[0]
 for s in teeth[1:]:pin=pin.fuse(s)
 pin=pin.cut(cyl(2.5,6,-23.5,-29.5,95)).removeSplitter()
 add('Pinion13','ZD 8195 / 13T 모터 피니언',pin,(.75,.43,.1),'https://www.zd-racing.com/home/934-zd-racing-9021-v3-upgrade-parts-motor-gears-13t-cnc-8195.html','13T published; module1, D5 bore and facewidth4 assumed. Pitch centers29.5mm provisional. Not a gear cutting drawing.')
 plate=box(-35,-54,68,3,49,54).cut(cyl(5.5,5,-36,-29.5,95)).cut(cyl(8,5,-36,0,95))
 for zz in (82.3,107.7):plate=plate.cut(cyl(1.7,5,-36,-29.5,zz))
 foot=box(-51,-54,68,16,49,3)
 for yy in (-47,-12):foot=foot.cut(Part.makeCylinder(1.7,5,V(-44,yy,67)))
 add('MotorBracketV05','모터 브래킷 제안 / 피치25.4',plate.fuse(foot).removeSplitter(),(.7,.72,.74),motorurl,'CUSTOM plate3mm; motor pitch25.4 published; chassis hole coordinates and stiffness unverified.')
 add('ESCTray','ESC 받침판',box(-75,83,248,70,55,3),(.65,.68,.7),'CUSTOM','CUSTOM upper deck mounting; screw locations pending')
 add('AXE_ESC','AXE PLUS R3 ESC / 30113201',box(-65,90,251,49.5,37.9,22.8),(.1,.12,.14),escurl,'Published overall49.5x37.9x32.8 including fan; main-body/fan split schematic. 135A manufacturer rating is not motor continuous torque.')
 add('ESCFan','ESC 냉각팬 공간',box(-52.75,96.45,273.8,25,25,10),(.25,.25,.27),escurl,'Published fan25x25x10; keep airflow clearance')
 # Replace battery placeholder using published supplier envelope.
 d.BatteryPack.Shape=box(-87,-21.5,160,154,43,25)
 d.BatteryPack.Label='Gens ace GEA503S60X6GT / 3S 5000mAh'
 d.BatteryPack.Evidence='Published154x43x25mm, 11.1V 5000mAh XT60; 55.5Wh nominal. Runtime and peak connector current not validated.'
 for i,x in enumerate((-60,35)):
  d.getObject('BatteryStrap'+str(i)).Shape=box(x,-24.5,160,15,49,28).cut(box(x-1,-21.5,159,17,43,26))
 d.recompute()
 oldlinks=[o for o in d.Objects if o.TypeId=='App::Link' and not o.Name.endswith('_EX') and o.Name not in replaced]
 overlaps=[]
 for o in new:
  for p in oldlinks:
   if o.Shape.BoundBox.intersect(p.Shape.BoundBox):
    v=o.Shape.common(p.Shape).Volume
    if v>.1:overlaps.append([o.Name,p.Name,round(v,3)])
 # Record rather than mask limitations in inherited simplified geometry.
 d.ComponentLibrary.Visibility=False;d.Exploded.Visibility=False;obsolete.Visibility=False
 d.RollingChassis.Visibility=True;d.RobotDeck.Visibility=True;d.Equipment.Visibility=True;d.BatteryEquipment.Visibility=True
 def snap(name):
  G.updateGui();loop=QtCore.QEventLoop();QtCore.QTimer.singleShot(800,loop.quit);loop.exec_()
  G.activeDocument().activeView().saveImage(OUT+'/'+name+'.png',1800,1400,'White')
 view=G.activeDocument().activeView();view.viewAxonometric();view.fitAll();snap('platform')
 d.RobotDeck.Visibility=False;d.Equipment.Visibility=False;d.BatteryEquipment.Visibility=False
 view.fitAll();snap('drivetrain')
 view.viewTop();view.fitAll();snap('drive_top')
 d.RobotDeck.Visibility=True;d.Equipment.Visibility=True;d.BatteryEquipment.Visibility=True
 view.viewAxonometric();view.fitAll()
 # Export visible assembly only, never original templates or superseded links.
 equip=[o for group in (d.Equipment,d.BatteryEquipment) for o in group.Group if o.TypeId=='Part::Feature']
 assembled=oldlinks+equip+new
 e=A.newDocument('ExportV05');resolved=[]
 for p in assembled:
  o=e.addObject('Part::Feature',p.Name);o.Shape=p.Shape.copy();o.Label=p.Label;resolved.append(o)
 Part.export(resolved,OUT+'/ZD9021V3_drive_review.step')
 s=Part.Shape();s.read(OUT+'/ZD9021V3_drive_review.step');assert s.isValid() and len(s.Solids)==sum(len(o.Shape.Solids) for o in resolved)
 A.closeDocument(e.Name);A.setActiveDocument(d.Name)
 # A3 orthographic drive layout in FreeCAD TechDraw.
 import TechDrawGui
 proj=d.addObject('Part::Feature','DrawingGeometry');proj.Shape=Part.makeCompound([box(-223,-66,65,446,132,3)]+[o.Shape for o in new]);proj.Visibility=False
 page=d.addObject('TechDraw::DrawPage','DriveDrawing');page.Label='09 A3 구동계 배치도 (검토용)'
 template=d.addObject('TechDraw::DrawSVGTemplate','DrawingTemplate')
 template.Template='/Applications/FreeCAD.app/Contents/Resources/share/Mod/TechDraw/Templates/ISO/A3_Landscape_blank.svg';page.Template=template
 for name,direction,x,y in [('Plan',V(0,0,1),155,165),('Side',V(0,-1,0),155,80)]:
  v=d.addObject('TechDraw::DrawViewPart',name);v.Source=[proj];v.Direction=direction;page.addView(v);v.ScaleType='Custom';v.Scale=.48;v.X=x;v.Y=y
 note=d.addObject('TechDraw::DrawViewAnnotation','DesignNotes');page.addView(note);note.X=340;note.Y=175;note.TextSize=3
 note.Text=['ZD9021-V3 / V05 DRIVE REVIEW','30 kg / 0.1 - 2 m/s TARGET','Motor: AXE4274 R3 1700KV','Body D42 x 74; shaft D5','ESC: AXE PLUS R3 / 135A','Envelope49.5 x37.9 x32.8','Battery3S / 5000mAh','154 x43 x25; XT60','ZD8195 13T / ZD8243 46T','Axle ratio38/11 ASSUMED','Total ratio12.224 ASSUMED','Pitch centers29.5 ASSUMED','Motor mount pitch25.4','Wheelbase370 / tire D145','Width430 / length550','NOT FOR MANUFACTURE','30kg capacity NOT VERIFIED','Speed feedback required']
 d.recompute();G.updateGui()
 loop=QtCore.QEventLoop();QtCore.QTimer.singleShot(5000,loop.quit);loop.exec_()
 d.recompute();TechDrawGui.exportPageAsSvg(page,OUT+'/drive_layout_A3.svg')
 proj.Visibility=False
 d.recompute();d.saveAs(OUT+'/ZD9021V3_drive_review.FCStd')
 json.dump({'shape_step_roundtrip':'PASS','new_vs_existing_overlap_mm3':overlaps,'performance':'UNVERIFIED:30kg load and0.1m/s operation','gear_ratio':'38/11 axle assumed; overall12.223776'},open(OUT+'/validation.json','w'),indent=2)
 A.closeDocument(d.Name);open(OUT+'/complete.txt','w').write('COMPLETE');G.getMainWindow().close()
except Exception:
 open(OUT+'/error.txt','w').write(traceback.format_exc());raise
