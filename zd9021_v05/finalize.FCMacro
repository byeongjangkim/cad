import FreeCAD as A, FreeCADGui as G, TechDrawGui
from PySide import QtCore
OUT='/Users/byeongjangkim/MyProjects/Robots/cad/zd9021_v05'
d=A.openDocument(OUT+'/ZD9021V3_drive_review.FCStd')
d.Side.Y=80
d.recompute();G.updateGui()
loop=QtCore.QEventLoop();QtCore.QTimer.singleShot(3000,loop.quit);loop.exec_()
TechDrawGui.exportPageAsSvg(d.DriveDrawing,OUT+'/drive_layout_A3.svg')
d.DrawingGeometry.Visibility=False
G.activeDocument().activeView().viewAxonometric();G.activeDocument().activeView().fitAll()
d.save();A.closeDocument(d.Name);G.getMainWindow().close()
