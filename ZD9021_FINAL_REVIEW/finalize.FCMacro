import FreeCAD as A, FreeCADGui as G, Part, TechDrawGui, json, traceback
from PySide6 import QtCore, QtGui, QtSvg
OUT='/Users/byeongjangkim/MyProjects/Robots/cad/ZD9021_FINAL_REVIEW'
try:
 d=A.openDocument('/Users/byeongjangkim/MyProjects/Robots/cad/zd9021_v05/ZD9021V3_drive_review.FCStd')
 G.activateView("Gui::View3DInventor", True)
 view=G.activeDocument().mdiViewsOfType("Gui::View3DInventor")[0]
 d.Label='ZD9021 통합 검토본 - 30kg / 0.1~2mps'
 d.DesignNotes.Text=[s.replace('0.1 - 5 m/s','0.1 - 2 m/s') for s in d.DesignNotes.Text]
 d.Side.Y=65;d.Plan.Y=205
 for n in ['ComponentLibrary','Exploded','Superseded','DrawingGeometry']:d.getObject(n).Visibility=False
 for n in ['RollingChassis','RobotDeck','Equipment','BatteryEquipment','SelectedDrive']:d.getObject(n).Visibility=True
 spec=d.addObject('Spreadsheet::Sheet','ReviewRequirements');spec.Label='00 최신 요구조건 및 미검증 항목'
 rows=[['항목','값','상태'],['총중량','30 kg','사용자 요구조건'],['최저속도','0.1 m/s','목표 / 실증 미완료'],['최고속도','2 m/s','목표 / 속도제한 미구현'],['타이어 외경','145 mm','설계값'],['총감속비','12.223776','차축 입력11T 가정'],['30kg 허용하중','미확인','순정 차체 및 현가 검증 필요'],['모터 연속토크','미확인','저속 부하 및 열 검증 필요'],['파일 용도','통합 설계 검토','구매·가공 확정 도면 아님']]
 for i,row in enumerate(rows,1):
  for col,value in zip('ABC',row):spec.set(col+str(i),value)
 spec.setColumnWidth('A',160);spec.setColumnWidth('B',160);spec.setColumnWidth('C',300)
 d.recompute();G.updateGui()
 def settle():
  loop=QtCore.QEventLoop();QtCore.QTimer.singleShot(3000,loop.quit);loop.exec()
 settle();TechDrawGui.exportPageAsSvg(d.DriveDrawing,OUT+'/Drive_Layout_A3.svg')
 # PDF from the actual exported vector drawing.
 renderer=QtSvg.QSvgRenderer(OUT+'/Drive_Layout_A3.svg')
 pdf=QtGui.QPdfWriter(OUT+'/Drive_Layout_A3.pdf');pdf.setPageSize(QtGui.QPageSize(QtGui.QPageSize.A3));pdf.setPageOrientation(QtGui.QPageLayout.Landscape);pdf.setPageMargins(QtCore.QMarginsF(0,0,0,0))
 painter=QtGui.QPainter(pdf);renderer.render(painter);painter.end()
 view.viewAxonometric();view.fitAll();settle();view.saveImage(OUT+'/Platform.png',1800,1400,'White')
 # Chassis view hides all upper equipment including ESC mounted on its own drive group.
 for n in ['RobotDeck','Equipment','BatteryEquipment','ESCTray','AXE_ESC','ESCFan']:d.getObject(n).Visibility=False
 view.fitAll();settle();view.saveImage(OUT+'/Drivetrain.png',1800,1400,'White')
 for n in ['RobotDeck','Equipment','BatteryEquipment','ESCTray','AXE_ESC','ESCFan']:d.getObject(n).Visibility=True
 view.viewAxonometric();view.fitAll();settle()
 excluded={'MotorMount8456','MotorAdapter8456','CenterSpur46T'}
 assembled=[o for o in d.Objects if o.TypeId=='App::Link' and not o.Name.endswith('_EX') and o.Name not in excluded]
 for name in ['Equipment','BatteryEquipment','SelectedDrive']:assembled.extend(o for o in d.getObject(name).Group if o.TypeId=='Part::Feature')
 assert all(o.Shape.isValid() and o.Shape.Volume>0 for o in assembled)
 e=A.newDocument('FinalExport');resolved=[]
 for p in assembled:
  o=e.addObject('Part::Feature',p.Name);o.Shape=p.Shape.copy();o.Label=p.Label;resolved.append(o)
 Part.export(resolved,OUT+'/ZD9021_Integrated_Review.step')
 check=Part.Shape();check.read(OUT+'/ZD9021_Integrated_Review.step')
 count=sum(len(o.Shape.Solids) for o in resolved)
 assert check.isValid() and len(check.Solids)==count
 A.closeDocument(e.Name);A.setActiveDocument(d.Name)
 G.activateView('Gui::View3DInventor',True)
 d.saveAs(OUT+'/ZD9021_Integrated_Review.FCStd')
 json.dump({'status':'PASS shape and STEP roundtrip','assembly_objects':len(assembled),'solids':count,'mass_target_kg':30,'speed_target_m_s':[0.1,2],'limitations':['30kg payload capability not verified','Minimum loaded speed and continuous motor torque unverified','No implemented speed limit','Axle input11T assumed','Mounts and reversed center gear layout unverified'],'hidden_groups':['ComponentLibrary','Exploded','Superseded','DrawingGeometry']},open(OUT+'/validation.json','w'),indent=2)
 A.closeDocument(d.Name)
 test=A.openDocument(OUT+'/ZD9021_Integrated_Review.FCStd')
 assert any('0.1 - 2 m/s' in s for s in test.DesignNotes.Text)
 assert all(not test.getObject(n).Visibility for n in ['ComponentLibrary','Exploded','Superseded','DrawingGeometry'])
 A.closeDocument(test.Name)
 open(OUT+'/complete.txt','w').write('Saved and reopened successfully; STEP roundtrip passed.')
 G.getMainWindow().close()
except Exception:
 open(OUT+'/error.txt','w').write(traceback.format_exc());raise
